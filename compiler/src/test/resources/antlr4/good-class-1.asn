TestModule DEFINITIONS ::= BEGIN

OPERATION ::= CLASS
{
   &ArgumentType OPTIONAL,
   &Errors ERROR OPTIONAL,
   &resultReturned BOOLEAN DEFAULT TRUE,
   &code INTEGER 
}

ERROR ::= CLASS
{
   &ParameterType OPTIONAL,
   &errorCode INTEGER UNIQUE
}
WITH SYNTAX
{
   [PARAMETER &ParameterType]
   CODE &errorCode
}

ProtocolExtensionContainer {S1AP-PROTOCOL-EXTENSION : ExtensionSetParam} ::= 
   SEQUENCE (SIZE (1..maxProtocolExtensions)) OF
   ProtocolExtensionField {{ExtensionSetParam}}

TABasedMDT ::= SEQUENCE {
   tAListforMDT TAListforMDT,
   iE-Extensions ProtocolExtensionContainer { {TABasedMDT-ExtIEs} } OPTIONAL,
   ...
}

ProtocolExtensionField {S1AP-PROTOCOL-EXTENSION : ExtensionSetParam} ::= SEQUENCE {
   id S1AP-PROTOCOL-EXTENSION.&id ({ExtensionSetParam}),
   criticality S1AP-PROTOCOL-EXTENSION.&criticality ({ExtensionSetParam}{@id}),
   extensionValue S1AP-PROTOCOL-EXTENSION.&Extension ({ExtensionSetParam}{@id})
}

S1AP-ELEMENTARY-PROCEDURE ::= CLASS {
   &InitiatingMessage,
   &SuccessfulOutcome OPTIONAL,
   &UnsuccessfulOutcome	OPTIONAL,
   &procedureCode ProcedureCode UNIQUE,
   &criticality Criticality DEFAULT ignore
}
WITH SYNTAX {
   INITIATING MESSAGE &InitiatingMessage
   [SUCCESSFUL OUTCOME &SuccessfulOutcome]
   [UNSUCCESSFUL OUTCOME &UnsuccessfulOutcome]
   PROCEDURE CODE &procedureCode
   [CRITICALITY	&criticality]
}

END
