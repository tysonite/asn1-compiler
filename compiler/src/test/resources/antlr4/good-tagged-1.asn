TestModule DEFINITIONS ::= BEGIN

Tt1 ::= [UNIVERSAL 0] IMPLICIT OCTET STRING
Tt2 ::= [APPLICATION 0] IMPLICIT OCTET STRING
Tt3 ::= [PRIVATE 0] IMPLICIT OCTET STRING
Tt4 ::= [0] IMPLICIT OCTET STRING
Tt5 ::= [0] EXPLICIT INTEGER
Tt6 ::= [0] BOOLEAN

Tt7 ::= [0] SEQUENCE {
   myVar1 [0] MyType1 DEFAULT v1,
   myVar2 [0] IMPLICIT MyType2 OPTIONAL,
   myVar3 [0] MyType3 OPTIONAL
}

END
