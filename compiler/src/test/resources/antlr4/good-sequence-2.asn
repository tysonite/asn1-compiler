TestModule DEFINITIONS ::= BEGIN

S1 ::= SEQUENCE SIZE(1..10) OF VisibleString
S2 ::= SEQUENCE SIZE(1..10) OF AbcDef
S3 ::= SEQUENCE SIZE(1..MAX) OF BOOLEAN
S4 ::= SEQUENCE SIZE(MIN..MAX) OF BOOLEAN
S5 ::= SEQUENCE SIZE(MIN..0) OF BOOLEAN

S6 ::= SEQUENCE {
   bs1 BIT STRING (CONTAINING My-Type-1) OPTIONAL
}

END
