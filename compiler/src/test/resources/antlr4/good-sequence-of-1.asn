TestModule DEFINITIONS ::= BEGIN

SO1 ::= SEQUENCE OF BOOLEAN
SO2 ::= SEQUENCE OF MyType

vso1 SEQUENCE OF INTEGER ::= { 1, 2, 3 }
vso2 SEQUENCE OF BOOLEAN ::= { TRUE, FALSE, TRUE }
vso3 SEQUENCE OF NULL ::= { NULL, NULL }
vso4 SEQUENCE OF OCTET STRING ::= { '0110'B, '1A2F'H }
vso5 SEQUENCE OF MyType ::= { abc, edf }

END
